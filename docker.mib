--
-- MIB generated by MG-SOFT Visual MIB Builder 2018 (64-bit) Version 12.0  Build 1200
-- Thursday, November 15, 2018 at 16:11:50
--

	ANDRE-GLOBAL-REG DEFINITIONS ::= BEGIN
 
		IMPORTS
			OBJECT-GROUP			
				FROM SNMPv2-CONF			
			enterprises, TimeTicks, OBJECT-TYPE, OBJECT-IDENTITY			
				FROM SNMPv2-SMI;
	
	
--
-- Node definitions
--
	
		-- 1.3.6.1.4.1.12345
		dockerRoot OBJECT-IDENTITY
			STATUS current
			DESCRIPTION 
				"The root of the OID sub-tree assigned to Company by the Internet Assigned Numbers Authority (IANA)"
			::= { enterprises 12345 }

		
		-- 1.3.6.1.4.1.12345.1
		dockerDaemon OBJECT IDENTIFIER ::= { dockerRoot 1 }

		
		-- 1.3.6.1.4.1.12345.1.1
		dockerDaemonUptime OBJECT-TYPE
			SYNTAX TimeTicks
			MAX-ACCESS read-only
			STATUS current
			DESCRIPTION
				"Docker Daemon total uptime."
			::= { dockerDaemon 1 }

		
		-- 1.3.6.1.4.1.12345.1.2
		dockerDaemonRestart OBJECT-TYPE
			SYNTAX INTEGER
				{
				notRestarting(0),
				restaring(1)
				}
			MAX-ACCESS read-write
			STATUS current
			DESCRIPTION
				"Check/set if docker Daemon is restarting."
			::= { dockerDaemon 2 }

		
		-- 1.3.6.1.4.1.12345.1.3
		dockerDaemonMandatoryImplementations OBJECT-GROUP
			OBJECTS { dockerDaemonUptime, dockerDaemonRestart }
			STATUS current
			DESCRIPTION 
				"Mandatory implementations of this MIB."
			::= { dockerDaemon 3 }

		
		-- 1.3.6.1.4.1.12345.2
		dockerContainers OBJECT IDENTIFIER ::= { dockerRoot 2 }

		
		-- 1.3.6.1.4.1.12345.2.1
		containeListTable OBJECT-TYPE
			SYNTAX SEQUENCE OF ContaineListEntry
			MAX-ACCESS not-accessible
			STATUS current
			DESCRIPTION
				"Contains information about containers currently running in docker Daemon."
			::= { dockerContainers 1 }

		
		-- 1.3.6.1.4.1.12345.2.1.1
		containeListEntry OBJECT-TYPE
			SYNTAX ContaineListEntry
			MAX-ACCESS not-accessible
			STATUS current
			DESCRIPTION
				"Description."
			INDEX { containeListHashIdentifier, containeListUptime, containeListName, containeListStatus }
			::= { containeListTable 1 }

		ContaineListEntry ::=
			SEQUENCE { 
				containeListHashIdentifier
					OCTET STRING,
				containeListUptime
					TimeTicks,
				containeListName
					OCTET STRING,
				containeListStatus
					INTEGER
			 }
			 
		-- 1.3.6.1.4.1.12345.2.1.1.1
		containeListHashIdentifier OBJECT-TYPE
			SYNTAX OCTET STRING
			MAX-ACCESS read-only
			STATUS current
			DESCRIPTION
				"Hash identifier of container."
			::= { containeListEntry 1 }
			 
		-- 1.3.6.1.4.1.12345.2.1.1.2
		containeListUptime OBJECT-TYPE
			SYNTAX TimeTicks
			MAX-ACCESS read-only
			STATUS current
			DESCRIPTION
				"Description."
			::= { containeListEntry 2 }

		-- 1.3.6.1.4.1.12345.2.1.1.3
		containeListName OBJECT-TYPE
			SYNTAX OCTET STRING
			MAX-ACCESS read-only
			STATUS current
			DESCRIPTION
				"Name of container."
			::= { containeListEntry 3 }

		-- 1.3.6.1.4.1.12345.2.1.1.4
		containeListStatus OBJECT-TYPE
			SYNTAX INTEGER
				{
				up(1),
				restarting(2),
				down(3)
				}
			MAX-ACCESS read-only
			STATUS current
			DESCRIPTION
				"Statur of container, Ex: Running, restarting, down, etc.."
			::= { containeListEntry 4 }

	
	END

--
